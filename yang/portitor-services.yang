// SPDX-FileCopyrightText: 2026 The Portitor contributors
// SPDX-License-Identifier: AGPL-3.0-or-later

submodule portitor-services {
  yang-version 1.1;
  belongs-to portitor { prefix pt; }
  import portitor-extensions { prefix px; }
  include portitor-types;

  description "Portitor configuration: services.";

  revision 2026-11-08 { description "First version, from the SQLite schema."; }

  grouping services {
    list ipam-prefix {
      key "prefix";
      action next-free {
        px:action "view";
        description "The prefix's next free address.";
        output {
          leaf address {
            type ip-address;
          }
        }
      }
      px:table "ipam_prefixes";
      px:parent-column "instance_id";
      description "IpamPrefix is a node in the prefix tree. Parent/child relations are not stored; they follow from CIDR containment within an instance.";
      leaf prefix {
        type ip-prefix;
      }
      leaf description {
        type text;
      }
      leaf dhcp-enabled {
        type boolean;
      }
      leaf dhcp-range-start {
        type ip-address;
      }
      leaf dhcp-range-end {
        type ip-address;
      }
      leaf dhcp-gateway {
        type ip-address;
      }
      leaf-list dhcp-dns-servers {
        type union { type leafref { path "../../../host/name"; } type leafref { path "../../../address-list/name"; } type ip-address; }
        ordered-by user;
      }
      leaf ra-enabled {
        type boolean;
        description "RaEnabled sends IPv6 router advertisements for the prefix on the interface that has an address in it; RaSlaac lets clients pick their own address (/64 only).";
      }
      leaf ra-slaac {
        type boolean;
      }
    }
    list ipam-address {
      key "address";
      px:table "ipam_addresses";
      px:parent-column "instance_id";
      description "IpamAddress is a single address. With DnsName it gets an A/AAAA record; with Mac also a DHCP reservation. The firewall's own addresses are configured on the interface (Interface.Addresses).";
      leaf address {
        type ip-address;
      }
      leaf dns-name {
        type domain-name;
      }
      leaf mac {
        type mac-address;
      }
      leaf description {
        type text;
      }
    }
    list dns-soa-template {
      key "name";
      px:table "dns_soa_templates";
      px:parent-column "instance_id";
      description "DnsSoaTemplate is a virtual firewall's own SOA template; the firewall's, for every virtual firewall, are the top-level dns-soa-template. Minimum is the SOA minimum (negative-caching TTL); the serial is dnsmgr2's.";
      uses dns-soa-template-fields;
    }
    list dnssec-policy {
      key "name";
      px:table "dns_dnssec_policies";
      px:parent-column "instance_id";
      description "DnsDnssecPolicy is a virtual firewall's own DNSSEC policy; the firewall's are the top-level dnssec-policy.";
      uses dnssec-policy-fields;
    }
    list dns-template {
      key "name";
      px:table "dns_templates";
      px:parent-column "instance_id";
      description "DnsTemplate is a virtual firewall's own zone template: SOA, default TTL, apex NS and an optional DNSSEC policy, its own or the firewall's (top level). The firewall's templates are the top-level dns-template.";
      leaf name {
        type string;
      }
      leaf soa-template {
        type union {
          type leafref { path "../../dns-soa-template/name"; }
          type leafref { path "../../../dns-soa-template/name"; }
        }
        px:column "soa_template_id";
      }
      leaf dnssec-policy {
        type union {
          type leafref { path "../../dnssec-policy/name"; }
          type leafref { path "../../../dnssec-policy/name"; }
        }
        px:column "dnssec_policy_id";
      }
      uses dns-template-fields;
    }
    list dns-zone {
      key "name";
      px:table "dns_zones";
      px:parent-column "instance_id";
      leaf name {
        type string;
      }
      leaf type {
        type enumeration { enum "forward"; enum "reverse4"; enum "reverse6"; enum "forward-only"; }
        default "forward";
      }
      leaf description {
        type text;
      }
      leaf dns-template {
        type union {
          type leafref { path "../../dns-template/name"; }
          type leafref { path "../../../dns-template/name"; }
        }
        px:column "dns_template_id";
        description "DnsTemplateID nil: built-in SOA and NS (localhost).";
      }
      leaf-list forwarders {
        type union { type leafref { path "../../../host/name"; } type leafref { path "../../../address-list/name"; } type ip-address; }
        ordered-by user;
        description "Forwarders: the DNS servers of a forward-only zone (addresses or named hosts).";
      }
      list record {
        key "id";
        ordered-by user;
        px:position "rank";
        px:table "dns_records";
        px:parent-column "zone_id";
        description "DnsRecord is one row of a zone's record grid, in Rank order. Type COMMENT (text in Value) and $DOMAIN (a subdomain in Name, applied to the rows below it) are editor-only; see builder.RecordName.";
        leaf id {
          type uint32;
        }
        leaf name {
          type string;
          mandatory true;
        }
        leaf ttl {
          type int64;
        }
        leaf type {
          type string;
          mandatory true;
        }
        leaf value {
          type string;
          description "Empty in a $DOMAIN row; a record of a type that needs one is refused without it.";
        }
        leaf mac {
          type string;
        }
        leaf description {
          type string;
        }
      }
    }
    list dns-blocklist {
      key "name";
      action update {
        px:action "operation";
        description "Downloads the blocklist again now, on its firewall (and an HA standby that answers).";
        output {
          leaf started {
            type string;
            description "What the firewall started on.";
          }
        }
      }
      px:table "dns_blocklists";
      px:parent-column "instance_id";
      description "DnsBlocklist is a list of domains the instance's DNS server does not resolve (fwconfig.DNSBlocklist), which the agent downloads from Urls.";
      leaf name {
        type string;
      }
      leaf description {
        type text;
      }
      leaf enabled {
        type boolean;
        default true;
      }
      leaf-list urls {
        type string;
        ordered-by user;
      }
      leaf auth-key {
        type string;
        px:secret;
        description "AuthKey fills {key} in the URLs. It is set through NewAuthKey (empty keeps it, ClearAuthKey removes it) and never sent back.";
      }
      leaf action {
        type enumeration { enum "nxdomain"; enum "nodata"; enum "drop"; enum "log"; }
        default "nxdomain";
        description "fwconfig.Blocklist*";
      }
      leaf refresh {
        type int32;
        default 720;
        description "minutes between downloads";
      }
    }
    list dns-update {
      key "name";
      px:table "dyndns_clients";
      px:parent-column "instance_id";
      description "DyndnsClient (a DNS update client) keeps DyndnsRecords in step with the addresses of an interface of its instance: on the nameserver Server by RFC 2136 UPDATE, or through the API of a DNS hosting Provider.";
      leaf name {
        type string;
      }
      leaf description {
        type text;
      }
      leaf enabled {
        type boolean;
        default true;
      }
      leaf interface {
        type leafref { path "../../interface/name"; }
        px:column "interface_id";
      }
      leaf server {
        type string;
      }
      leaf zone {
        type domain-name;
        mandatory true;
      }
      leaf tsig-name {
        type domain-name;
      }
      leaf tsig-algorithm {
        type string;
      }
      leaf tsig-secret {
        type string;
        px:secret;
        description "TsigSecret is set through NewTsigSecret and never sent back.";
      }
      leaf retry-interval {
        type int32;
      }
      leaf verify-interval {
        type int32;
      }
      leaf provider {
        type string;
        default "rfc2136";
        description "Provider is a fwconfig.DNSProviders name.";
      }
      list provider-setting {
        key "name";
        px:json-map "provider_settings";
        description "ProviderSettings are the provider's fields, secrets included; never sent back. They are written through Settings.";
        leaf name { type string; }
        leaf value { type string; px:secret; }
      }
      list record {
        key "id";
        px:table "dyndns_records";
        px:parent-column "client_id";
        description "DyndnsRecord is a record a DyndnsClient maintains. A/AAAA without Value follow the interface; TXT without Value holds the last update time.";
        leaf id {
          type uint32;
        }
        leaf name {
          type string;
          mandatory true;
        }
        leaf type {
          type string;
          mandatory true;
        }
        leaf ttl {
          type int32;
        }
        leaf value {
          type string;
        }
        leaf description {
          type string;
        }
      }
    }
    list certificate {
      key "name";
      action chain {
        px:action "view";
        description "What an imported certificate's chain says, and whether the certificate has its key.";
        output {
          leaf is-ca {
            type boolean;
          }
          leaf issuer {
            type string;
          }
          leaf-list chain {
            type string;
            ordered-by user;
            description "The certification path, the certificate first.";
          }
          leaf not-before {
            type string;
          }
          leaf not-after {
            type string;
          }
          leaf has-key {
            type boolean;
          }
        }
      }
      action renew {
        px:action "operation";
        description "Orders an ACME certificate now, on its firewall (and its HA standby, which copies it).";
        output {
          leaf started {
            type string;
            description "What the firewall started on.";
          }
        }
      }
      action generate {
        px:action "create";
        description "Makes the certificate's key and chain here: self-signed, or signed by one of the firewall's certificate authorities (global admins only).";
        input {
          leaf-list domains {
            type string;
            ordered-by user;
            description "DNS names (*.example.com too) and IP addresses.";
          }
          leaf common-name {
            type text { length "0..64"; }
            description "The subject's common name; the first domain when empty.";
          }
          leaf key-type {
            type cert-key-type;
            default "ec256";
          }
          leaf days {
            type int32 { range "1..36500"; }
            default 365;
          }
          leaf signed-by {
            type string;
            description "The firewall's certificate authority (certificate-authority) that signs it; self-signed when empty.";
          }
        }
      }
      px:table "certificates";
      px:parent-column "instance_id";
      description "Certificate is a TLS certificate the agent gets from an ACME CA (Let's Encrypt) and renews, the CA's HTTP-01 requests coming in on Interface; or one imported with its key (Source fwconfig.CertSourceImport), which has no ACME settings and no interface.";
      leaf name {
        type string;
      }
      leaf description {
        type text;
      }
      leaf enabled {
        type boolean;
        default true;
      }
      leaf source {
        type enumeration { enum "acme"; enum "import"; }
        default "acme";
      }
      leaf-list domains {
        type string;
        ordered-by user;
        description "Domains of an imported certificate are its SANs, read from it.";
      }
      leaf common-name {
        type string;
      }
      leaf email {
        type email;
      }
      leaf ca {
        type string;
        default "letsencrypt";
        description "Ca is a fwconfig.ACMECAs name or an ACME directory URL.";
      }
      leaf key-type {
        type cert-key-type;
        default "ec256";
      }
      leaf challenge {
        type enumeration { enum "http-01"; enum "dns-01"; }
        default "http-01";
      }
      leaf interface {
        type leafref { path "../../interface/name"; }
        px:column "interface_id";
        description "InterfaceID is HTTP-01's, DyndnsClientID DNS-01's: the DNS update client whose provider writes the TXT records.";
      }
      leaf full-chain {
        type string;
        description "FullChain and PrivKey are an imported certificate's PEM chain and key. The key is set through NewPrivKey and never shown.";
      }
      leaf priv-key {
        type string;
        px:secret;
      }
      leaf dns-update {
        type leafref { path "../../dns-update/name"; }
        px:column "dyndns_client_id";
      }
    }
    list acme-proxy-policy {
      key "name";
      px:table "acme_proxy_policies";
      px:parent-column "instance_id";
      description "AcmeProxyPolicy allows the ACME proxy's clients in Sources (any when empty; hosts/prefixes by name) names in Domains (\"host.example.com\", or \"*.example.com\" for any name below it), got upstream by Challenge: DNS-01, whose TXT records the DyndnsClient's provider writes, or HTTP-01, answered by the firewall on port 80 of the Interface. Policies are tried by name; a disabled one is left out.";
      leaf name {
        type string;
      }
      leaf enabled {
        type boolean;
        default true;
      }
      leaf description {
        type text;
      }
      leaf-list domains {
        type string;
        ordered-by user;
      }
      leaf-list sources {
        type union { type leafref { path "../../../host/name"; } type leafref { path "../../../address-list/name"; } type cidr; }
        ordered-by user;
      }
      leaf challenge {
        type enumeration { enum "http-01"; enum "dns-01"; }
        default "dns-01";
      }
      leaf interface {
        type leafref { path "../../interface/name"; }
        px:column "interface_id";
      }
      leaf dns-update {
        type leafref { path "../../dns-update/name"; }
        px:column "dyndns_client_id";
      }
    }
    list snmp-user {
      key "name";
      px:table "snmp_users";
      px:parent-column "instance_id";
      description "SnmpUser is a read-only SNMPv3 user of an instance. Disabled, it is left out.";
      leaf name {
        type string;
      }
      leaf enabled {
        type boolean;
        default true;
      }
      leaf description {
        type text;
      }
      leaf auth-protocol {
        type string;
        default "SHA-256";
      }
      leaf auth-password {
        type string;
        px:secret;
      }
      leaf priv-protocol {
        type string;
        description "PrivProtocol empty: authentication only (authNoPriv). A new user gets AES from the GUI; no default here, which would make empty impossible.";
      }
      leaf priv-password {
        type string;
        px:secret;
      }
    }
  }

  grouping dns-soa-template-fields {
    leaf name {
      type string;
    }
    leaf mname {
      type domain-name;
      mandatory true;
    }
    leaf rname {
      type string;
      mandatory true;
    }
    leaf refresh {
      type int64;
      default 86400;
    }
    leaf retry {
      type int64;
      default 7200;
    }
    leaf expire {
      type int64;
      default 3600000;
    }
    leaf minimum {
      type int64;
      default 3600;
    }
  }

  grouping dnssec-policy-fields {
    leaf name {
      type string;
    }
    leaf ksk-lifetime {
      type string;
    }
    leaf ksk-algorithm {
      type string;
      mandatory true;
    }
    leaf zsk-lifetime {
      type string;
    }
    leaf zsk-algorithm {
      type string;
      mandatory true;
    }
    leaf purge-keys {
      type string;
    }
    leaf signatures-validity {
      type string;
    }
    leaf signatures-validity-dnskey {
      type string;
    }
    leaf signatures-refresh {
      type string;
    }
  }

  grouping dns-template-fields {
    leaf default-ttl {
      type int64;
      default 3600;
    }
    list nameserver {
      key "name address";
      ordered-by user;
      px:json "nameservers";
      leaf name {
        type domain-name;
      }
      leaf address {
        type union { type ip-address; type string { length "0"; } }
      }
    }
    leaf description {
      type text;
    }
  }

  // What is the firewall's, not a virtual firewall's: the servers its
  // journal goes to, its certificate authorities, and the DNS templates
  // every virtual firewall may use.
  grouping firewall-services {
    list syslog-server {
      key "id";
      px:table "syslog_servers";
      description "SyslogServer is a remote syslog server rsyslog sends the firewall's journal to (the host's, with every virtual firewall's logs). Disabled, it is left out.";
      leaf id {
        type uint32;
      }
      leaf enabled {
        type boolean;
        default true;
      }
      leaf description {
        type text;
      }
      leaf address {
        type ip-address;
        mandatory true;
      }
      leaf port {
        type int32;
        default 514;
      }
      leaf protocol {
        type string;
        default "udp";
        description "Protocol, Format and Severity are fwconfig.SyslogProtocols', SyslogFormats' and SyslogSeverities'.";
      }
      leaf format {
        type string;
        default "rfc3164";
      }
      leaf severity {
        type string;
        default "info";
      }
    }
    list certificate-authority {
      key "name";
      description "A certificate authority of the firewall: imported with its key, or made by generate. It signs the virtual firewalls' certificates (their generate's signed-by) and stays in portitor-config: it is not deployed. Global admins only.";
      action chain {
        px:action "view";
        description "What the CA's chain says, and whether it has its key.";
        output {
          leaf is-ca {
            type boolean;
          }
          leaf issuer {
            type string;
          }
          leaf-list chain {
            type string;
            ordered-by user;
            description "The certification path, the certificate first.";
          }
          leaf not-before {
            type string;
          }
          leaf not-after {
            type string;
          }
          leaf has-key {
            type boolean;
          }
        }
      }
      action generate {
        px:action "create";
        description "Makes a self-signed CA here, its key and certificate.";
        input {
          leaf common-name {
            type text { length "0..64"; }
            description "The subject's common name; the CA's name when empty.";
          }
          leaf key-type {
            type cert-key-type;
            default "ec256";
          }
          leaf days {
            type int32 { range "1..36500"; }
            default 3650;
          }
        }
      }
      leaf name {
        type string;
      }
      leaf description {
        type text;
      }
      leaf full-chain {
        type string;
        description "The CA's certificate (and those above it) in PEM.";
      }
      leaf priv-key {
        type string;
        px:secret;
        description "The CA's key in PEM, never shown.";
      }
    }
    list dns-soa-template {
      key "name";
      px:table "dns_soa_templates";
      description "The firewall's SOA templates, for the firewall's DNS templates and every virtual firewall's own.";
      uses dns-soa-template-fields;
    }
    list dnssec-policy {
      key "name";
      px:table "dns_dnssec_policies";
      description "The firewall's DNSSEC policies, for the firewall's DNS templates and every virtual firewall's own.";
      uses dnssec-policy-fields;
    }
    list dns-template {
      key "name";
      px:table "dns_templates";
      description "The firewall's zone templates, which every virtual firewall's zones may use. Their SOA template and DNSSEC policy are the firewall's too.";
      leaf name {
        type string;
      }
      leaf soa-template {
        type leafref { path "../../dns-soa-template/name"; }
        px:column "soa_template_id";
      }
      leaf dnssec-policy {
        type leafref { path "../../dnssec-policy/name"; }
        px:column "dnssec_policy_id";
      }
      uses dns-template-fields;
    }
  }
}
